// SPDX-License-Identifier: BSD-2-Clause
module frr-bgp-types {
  yang-version 1.1;
  namespace "http://frrouting.org/yang/bgp-types";
  prefix frr-bt;

  organization
    "FRRouting";
  contact
    "FRR Users List: <mailto:frog@lists.frrouting.org> FRR Development
     List: <mailto:dev@lists.frrouting.org>";
  description
    "This module contains general data definitions for use in BGP.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2026-07-26 {
    description
      "Add FRR CLI-syntax route-target and route-distinguisher typedefs.";
    reference
      "FRRouting";
  }

  revision 2026-07-21 {
    description
      "Add BGP Open Policy role typedef for neighbor local-role CLI.";
    reference
      "FRRouting";
  }

  revision 2019-12-03 {
    description
      "Initial revision.";

    reference
      "FRRouting";
  }

  typedef plist-ref {
    type string;
    description
      "Reference to a plist.";
  }

  typedef access-list-ref {
    type string;
    description
      "Reference to an access list.";
  }

  typedef as-path-filter-ref {
    type string;
    description
      "Reference to an AS path filter, which specifies a filter for AS paths in BGP routing.";
  }

  typedef bgp-instance-type {
    type enumeration {
      enum "default" {
        value 1;
        description
          "BGP instance default.";
      }
      enum "vrf" {
        value 2;
        description
          "BGP instance vrf.";
      }
      enum "view" {
        value 3;
        description
          "BGP instance view.";
      }
    }
    description
      "BGP instance type, which specifies the type of BGP instance.";
  }

  typedef as-type {
    type enumeration {
      enum "as-specified" {
        value 1;
        description
          "AS has explicitly specified value.";
      }
      enum "internal" {
        value 2;
        description
          "Internal BGP peer.";
      }
      enum "external" {
        value 3;
        description
          "External BGP peer.";
      }
      enum "auto" {
        value 4;
        description
          "Auto-detect remote AS from peer's OPEN message.
           Maps to: neighbor <peer> remote-as auto.";
      }
    }
    description
      "AS type, which specifies the type of AS or BGP peer.";
  }

  typedef add-path-type {
    type enumeration {
      enum "all" {
        value 1;
        description
          "To advertise all paths to a neighbor.";
      }
      enum "per-as" {
        value 2;
        description
          "To advertise the best path per each neighboring AS.";
      }
      enum "none" {
        value 3;
        description
          "Add path feature is disabled.";
      }
      enum "best-selected" {
        value 4;
        description
          "Advertise a configured number of best selected paths.
           Maps to: neighbor <peer> addpath-tx-best-selected <1-6>.";
      }
    }
    description
      "Add path type, which specifies how paths are advertised to a neighbor.";
  }

  typedef bfd-session-type {
    type enumeration {
      enum "single-hop" {
        value 1;
        description
          "Single hop session.";
      }
      enum "multi-hop" {
        value 2;
        description
          "Multiple hop session.";
      }
      enum "not-configured" {
        value 3;
        description
          "Not Configured.";
      }
    }
    description
      "BFD session type, which can be single-hop, multi-hop, or not-configured.";
  }

  typedef direction {
    type enumeration {
      enum "in" {
        value 1;
        description
          "IN, ingress, Rx.";
      }
      enum "out" {
        value 2;
        description
          "OUT, egress, Tx.";
      }
    }
    description
      "Direction of traffic flow, either ingress or egress.";
  }

  typedef bgp-role {
    type enumeration {
      enum provider {
        description
          "Local speaker provides transit to the remote peer.";
      }
      enum rs-server {
        description
          "Local speaker is a route server for the remote peer.";
      }
      enum rs-client {
        description
          "Local speaker is a route server client.";
      }
      enum customer {
        description
          "Local speaker receives transit from the remote peer.";
      }
      enum peer {
        description
          "Local speaker and remote peer have a lateral peering
           relationship.";
      }
    }
    description
      "BGP Open Policy role as defined by RFC 9234.";
  }

  /*
   * FRR CLI RD/RT syntax (not IETF ietf-routing-types).
   * Matches ASN:NN_OR_IP-ADDRESS:NN and AA.BB:NN as used by bgpd CLI.
   * Fine-grained validation is performed by str2prefix_rd /
   * ecommunity_str2com in northbound VALIDATE callbacks.
   *
   * Patterns: IPv4:NN | AA.BB:NN | ASN:NN  (plus *:NN for route-target).
   * Do not put comments between '+' string fragments; libyang rejects that.
   */
  typedef route-distinguisher {
    type string {
      /*
       * Loose CLI-syntax gate matching ASN:NN / AA.BB:NN / A.B.C.D:NN
       * and inet_aton-lenient forms such as 100.100.100:100.
       * Real validation is done by str2prefix_rd() in NB callbacks.
       */
      pattern '[^: \t]+:[0-9]{1,10}';
    }
    description
      "FRR route distinguisher as accepted by CLI
       (ASN:NN, AA.BB:NN, or A.B.C.D:NN; inet_aton-lenient IPv4).";
  }

  typedef route-target {
    type string {
      /*
       * Loose CLI-syntax gate; also accepts *:NN for EVPN VRF import.
       * Real validation is done by ecommunity_str2com() in NB callbacks.
       */
      pattern '[^: \t]+:[0-9]{1,10}';
    }
    description
      "FRR route target as accepted by CLI
       (ASN:NN, AA.BB:NN, A.B.C.D:NN, or *:NN for EVPN VRF import).";
  }
}
